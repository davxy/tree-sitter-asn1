-- Simplified LDAP definitions (based on RFC 4511)
Lightweight-Directory-Access-Protocol-V3 { 1 3 6 1 1 18 }

DEFINITIONS IMPLICIT TAGS ::=

BEGIN

LDAPMessage ::= SEQUENCE {
    messageID       MessageID,
    protocolOp      CHOICE {
        bindRequest     BindRequest,
        bindResponse    BindResponse,
        searchRequest   SearchRequest,
        searchResEntry  SearchResultEntry,
        searchResDone   SearchResultDone,
        modifyRequest   ModifyRequest,
        modifyResponse  ModifyResponse,
        addRequest      AddRequest,
        addResponse     AddResponse,
        delRequest      DelRequest,
        delResponse     DelResponse
    },
    controls        [0] Controls OPTIONAL
}

MessageID ::= INTEGER (0..2147483647)

LDAPString ::= OCTET STRING

LDAPOID ::= OCTET STRING

LDAPDN ::= LDAPString

AttributeDescription ::= LDAPString

BindRequest ::= [APPLICATION 0] SEQUENCE {
    version         INTEGER (1..127),
    name            LDAPDN,
    authentication  AuthenticationChoice
}

AuthenticationChoice ::= CHOICE {
    simple          [0] OCTET STRING,
    sasl            [3] SaslCredentials
}

SaslCredentials ::= SEQUENCE {
    mechanism       LDAPString,
    credentials     OCTET STRING OPTIONAL
}

BindResponse ::= [APPLICATION 1] SEQUENCE {
    resultCode      LDAPResult,
    matchedDN       LDAPDN,
    diagnosticMessage LDAPString
}

LDAPResult ::= ENUMERATED {
    success                      (0),
    operationsError              (1),
    protocolError                (2),
    timeLimitExceeded            (3),
    sizeLimitExceeded            (4),
    authMethodNotSupported       (7),
    strongerAuthRequired         (8),
    noSuchAttribute              (16),
    invalidAttributeSyntax       (21),
    noSuchObject                 (32),
    invalidDNSyntax              (34),
    inappropriateAuthentication  (48),
    invalidCredentials           (49),
    insufficientAccessRights     (50),
    busy                         (51),
    unavailable                  (52),
    unwillingToPerform           (53),
    other                        (80),
    ...
}

SearchRequest ::= [APPLICATION 3] SEQUENCE {
    baseObject   LDAPDN,
    scope        ENUMERATED {
        baseObject              (0),
        singleLevel             (1),
        wholeSubtree            (2),
        ...
    },
    derefAliases ENUMERATED {
        neverDerefAliases       (0),
        derefInSearching        (1),
        derefFindingBaseObj     (2),
        derefAlways             (3)
    },
    sizeLimit    INTEGER (0..2147483647),
    timeLimit    INTEGER (0..2147483647),
    typesOnly    BOOLEAN,
    filter       Filter,
    attributes   AttributeSelection
}

AttributeSelection ::= SEQUENCE OF LDAPString

Filter ::= CHOICE {
    and             [0] SET OF Filter,
    or              [1] SET OF Filter,
    not             [2] Filter,
    equalityMatch   [3] AttributeValueAssertion,
    substrings      [4] SubstringFilter,
    greaterOrEqual  [5] AttributeValueAssertion,
    lessOrEqual     [6] AttributeValueAssertion,
    present         [7] AttributeDescription,
    approxMatch     [8] AttributeValueAssertion
}

AttributeValueAssertion ::= SEQUENCE {
    attributeDesc   AttributeDescription,
    assertionValue  AssertionValue
}

AssertionValue ::= OCTET STRING

SubstringFilter ::= SEQUENCE {
    type        AttributeDescription,
    substrings  SEQUENCE OF SubstringChoice
}

SubstringChoice ::= CHOICE {
    initial [0] AssertionValue,
    any     [1] AssertionValue,
    final   [2] AssertionValue
}

SearchResultEntry ::= [APPLICATION 4] SEQUENCE {
    objectName  LDAPDN,
    attributes  PartialAttributeList
}

PartialAttributeList ::= SEQUENCE OF PartialAttribute

PartialAttribute ::= SEQUENCE {
    type    AttributeDescription,
    vals    SET OF AttributeValue
}

AttributeValue ::= OCTET STRING

SearchResultDone ::= [APPLICATION 5] LDAPResult

Controls ::= SEQUENCE OF Control

Control ::= SEQUENCE {
    controlType     LDAPOID,
    criticality     BOOLEAN DEFAULT FALSE,
    controlValue    OCTET STRING OPTIONAL
}

ModifyRequest ::= [APPLICATION 6] SEQUENCE {
    object          LDAPDN,
    changes         SEQUENCE OF ModifyChange
}

ModifyChange ::= SEQUENCE {
    operation       ENUMERATED {
        add     (0),
        delete  (1),
        replace (2),
        ...
    },
    modification    PartialAttribute
}

ModifyResponse ::= [APPLICATION 7] LDAPResult

AddRequest ::= [APPLICATION 8] SEQUENCE {
    entry           LDAPDN,
    attributes      AttributeList
}

AttributeList ::= SEQUENCE OF Attribute

Attribute ::= SEQUENCE {
    type    AttributeDescription,
    vals    SET OF AttributeValue
}

AddResponse ::= [APPLICATION 9] LDAPResult

DelRequest ::= [APPLICATION 10] LDAPDN

DelResponse ::= [APPLICATION 11] LDAPResult

END
